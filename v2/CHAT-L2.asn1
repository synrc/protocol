--- Протокол Месенжера Сохацького v2 для паб-саб брокерів на TLS
--- https://tonpa.guru/stream/2023/2023-08-07%20CHAT%20ASN.1.htm

CHAT-L2 DEFINITIONS IMPLICIT TAGS ::=
BEGIN
    -- CHAT-v2 design direction
    --
    -- Архітектурна мета:
    --   1. CHATProtocol містить тільки transport-level packet types.
    --   2. Message описує тільки контент повідомлення.
    --   3. Event є єдиним каналом runtime-подій (ack/activity/state updates).
    --   4. Query є єдиним request/response механізмом.
    --   5. Domain сутності (Subscription, Person, Member, Conference, Roster, Inbox view)
    --      не повинні бути top-level packet types.
    --
    -- Тобто одна семантика не повинна мати кілька паралельних wire-шляхів.

    IMPORTS ContentInfo FROM CryptographicMessageSyntax-2009
            CertificationRequest FROM PKCS-10
            Certificate FROM PKIX1Explicit-2009 ;

    Version ::= INTEGER  { v0(0), v1(1), v2(2), v3(3) }
    Flavour ::= ENUMERATED { apple (1), microsoft (2), google (3), ericsson (4), nokia (5), cisco (6) }
    Binary  ::= OCTET STRING

    -- 01 Authority (CA)

    Feature ::= SEQUENCE { id OCTET STRING, key OCTET STRING, value OCTET STRING, group OCTET STRING }
    AuthorityMethod ::= ENUMERATED { announce (0), enroll (1), authenticate (2), revoke (3), renew (4), ... }
    Authority ::= SEQUENCE {
       id OCTET STRING,
       vsn Version,
       session OCTET STRING,
       type AuthorityMethod,
       cert ANY,
       settings SEQUENCE OF feature Feature,
        ... }

    -- 02 Message (MNESIA, SQLite)

    -- Message описує тільки саме повідомлення і його вміст.
    -- Event є уніфікованим типом для всіх подій (Ack + Activity).
    -- Такий поділ мінімізує розмір базових повідомлень і не змішує семантику.

    MessageType ::= ENUMERATED { normal (0), sys (1), reply (2), forward (3), ... }

    MessageFeed ::= CHOICE { private [1] Privatebox, chan [2] Streambox, mailbox [4] Mailbox, group [8] Groupbox, ... }

    File ::= SEQUENCE {
       id OCTET STRING,
       mime OCTET STRING,
       payload ContentInfo,
       parentid OCTET STRING }

    Message ::= SEQUENCE {
       id Binary,
       vsn Version,
       session Binary,
       feed MessageFeed,
       payload ContentInfo,
       type MessageType OPTIONAL,
       link Binary OPTIONAL,
       files [0] SEQUENCE OF file File OPTIONAL,
       mentioned [1] SEQUENCE OF name Binary OPTIONAL,
       ...
    }

    -- 03 Inbox Folder Queue (MNESIA, SQLite) /Mail /Chat

    Privatebox ::= SEQUENCE { address OCTET STRING }
    Streambox ::= SEQUENCE { channel OCTET STRING }
    Groupbox ::= SEQUENCE { channel OCTET STRING }
    Mailbox ::= SEQUENCE { channel OCTET STRING }

    InboxMethod ::= ENUMERATED { get (1), erase (2), ...}

    Inbox ::= SEQUENCE {
       id OCTET STRING,
       vsn Version,
       session OCTET STRING,
       type InboxMethod,
       feed MessageFeed,
       messages [0] SEQUENCE OF message Message OPTIONAL,
        ... }

    InboxOp ::= ENUMERATED {
       get   (1),
       erase (2),
       ...
    }

    -- get/erase працюють у межах конкретного feed
    -- для обох операцій feed очікується
    InboxQuery ::= SEQUENCE {
       op    InboxOp,
       feed  [0] MessageFeed OPTIONAL,
       ...
    }

    InboxItem ::= SEQUENCE {
       message Message
    }

    -- result повертає набір елементів inbox для feed (може бути пустим)
    InboxAnswer ::= SEQUENCE {
       items [0] SEQUENCE OF item InboxItem OPTIONAL,
       ...
    }

    -- 04 Event (Ack + Activity fusion)
    --
    -- Event є єдиним каналом runtime-подій.
    -- Події групуються за family payload, без глобального плаского enum.
    -- Для простих family тип події задається локальним enum усередині payload.

    MessageEventType ::= ENUMERATED {
       received  (1),
       delivered (2),
       read      (3),
       edited    (4),
       deleted   (5),
       updated   (6), ...}

    MessageEvent ::= SEQUENCE {
       type       MessageEventType,
       messageId  [0] OCTET STRING OPTIONAL,
       feed       [1] MessageFeed OPTIONAL,
       actor      [2] OCTET STRING OPTIONAL,
       timestamp  [3] INTEGER OPTIONAL,
       ...
    }

    PresenceEventType ::= ENUMERATED {
       online   (1),
       offline  (2),
       typing   (3), ...}

    PresenceEvent ::= SEQUENCE {
       type       PresenceEventType,
       feed       [0] MessageFeed OPTIONAL,
       actor      [1] OCTET STRING OPTIONAL,
       timestamp  [2] INTEGER OPTIONAL,
       ...
    }

    EventPayload ::= CHOICE {
       message   [1] MessageEvent,
       presence  [2] PresenceEvent
    }

    Event ::= SEQUENCE {
       id OCTET STRING,
       vsn Version,
       session OCTET STRING,
       payload EventPayload,
       ...
    }

    -- Query є єдиним request/response шаром протоколу.
    -- Усі commands і state-запити повинні йти через Query.
    -- Payload уже розбитий на доменні family envelope.
    -- Внутрішні request/result payload типи тимчасово залишаються opaque
    -- до поступової типізації кожної family окремо.

    QueryType ::= ENUMERATED {
       get    (1),
       set    (2),
       result (3),
       error  (4), ...}

    Query ::= SEQUENCE {
       id OCTET STRING,
       vsn Version,
       session OCTET STRING,

       queryType QueryType,

       refId [0] OCTET STRING OPTIONAL, -- request correlation id
       feed [1] MessageFeed OPTIONAL,
       target [2] OCTET STRING OPTIONAL, -- optional routing hint; domain target belongs in payload
       payload [3] QueryPayload OPTIONAL, -- typed query family payload
       code [4] INTEGER OPTIONAL,
       ...
    }

    QueryPayload ::= CHOICE {
       subscription [1] SubscriptionCore,
       presence     [2] PresenceCore,
       person       [3] PersonCore,
       roster       [4] RosterCore,
       member       [5] MemberExtension,
       conference   [6] ConferenceExtension,
       moderation   [7] ModerationExtension,
       inbox        [8] InboxExtension,
       search       [9] SearchExtension,
       bpe          [10] ProcessExtension,
       kvs          [11] StorageExtension,
       mail         [12] MailExtension, -- X.420
       ...
    }

    ProcessExtension ::= CHOICE { request [1] OCTET STRING, result [2] OCTET STRING }
    StorageExtension ::= CHOICE { request [1] OCTET STRING, result [2] OCTET STRING }
    MailExtension    ::= CHOICE { request [1] OCTET STRING, result [2] OCTET STRING }

    SubscriptionCore ::= CHOICE {
       request [1] SubscriptionQuery,
       result  [2] SubscriptionAnswer
    }

    PresenceCore ::= CHOICE {
       request [1] PresenceQuery,
       result  [2] PresenceAnswer
    }

    PersonCore ::= CHOICE {
       request [1] PersonQuery,
       result  [2] PersonAnswer
    }

    MemberExtension ::= CHOICE {
       request [1] MemberQuery,
       result  [2] MemberAnswer
    }

    InboxExtension ::= CHOICE {
       request [1] InboxQuery,
       result  [2] InboxAnswer
    }

    -- 05 Search (LDAP Search)

    SearchStatus ::= ENUMERATED { ok (0), ...}
    Criteria ::= ENUMERATED { equal (0), notequal (1), like (2), ...}
    Scope ::= ENUMERATED { profile (0), folder (1), contact (2), member (3), room (4), chat (5), message (6), ...}

    SearchOp ::= ENUMERATED {
       execute (1),
       list    (2),
       ...
    }

    -- execute використовує field/value/criteria/type
    -- list допускає частковий фільтр або перегляд у межах scope/dn
    SearchQuery ::= SEQUENCE {
       op       SearchOp,
       dn       [0] OCTET STRING OPTIONAL,
       field    [1] OCTET STRING OPTIONAL,
       value    [2] OCTET STRING OPTIONAL,
       criteria [3] Criteria OPTIONAL,
       type     [4] Scope OPTIONAL,
       ...
    }

    SearchItem ::= SEQUENCE {
       dn       [0] OCTET STRING OPTIONAL,
       field    [1] OCTET STRING OPTIONAL,
       value    [2] OCTET STRING OPTIONAL,
       criteria [3] Criteria OPTIONAL,
       type     [4] Scope OPTIONAL
    }

    -- result повертає список знайдених елементів (може бути пустим)
    SearchAnswer ::= SEQUENCE {
       items [0] SEQUENCE OF item SearchItem OPTIONAL,
       ...
    }

    SearchExtension ::= CHOICE {
       request [1] SearchQuery,
       result  [2] SearchAnswer
    }

    -- 06 Subscription (зв'язок підписки між суб'єктом і ціллю)
    --
    -- Модель спрощена до факту зв'язку (actor -> target).
    -- Жодних статусів або presence тут більше немає.
    --
    -- Перенесення семантики:
    --
    -- Presence (online/offline/typing):
    --   → перенесено в Event
    --
    -- Lifecycle дії (request/confirm/ignore/ban/unban):
    --   → передаються через Event (як події)
    --   → або ініціюються через Query (type=set)
    --
    -- Бан:
    --   → не є частиною Subscription
    --   → є server-side policy (обмеження доступу)
    --   → встановлюється через Query і сигналізується через Event
    --
    -- Таким чином:
    --   Subscription = state (факт зв'язку)
    --   Event        = що сталося (події)
    --   Query        = як це змінити / отримати

    Subscription ::= SEQUENCE {
       actor  Binary,
       target Binary,
       ...
    }

    -- get/create/remove очікують actor + target
    -- list допускає частковий фільтр
    SubscriptionQuery ::= SEQUENCE {
       op     SubscriptionOp,
       actor  [0] Binary OPTIONAL,
       target [1] Binary OPTIONAL,
       ...
    }

    SubscriptionOp ::= ENUMERATED {
       get    (1),
       list   (2),
       create (3),
       remove (4),
       ...
    }

    -- get/create/remove зазвичай повертають item
    -- list повертає items
    SubscriptionAnswer ::= SEQUENCE {
       item   [0] Subscription OPTIONAL,
       items  [1] SEQUENCE OF subscription Subscription OPTIONAL,
       ...
    }

    -- 07 Roster (LDAP /People, /Channels, /Topics and /Servers user sub-folders)

    -- Presence як snapshot-стан для roster/member.
    -- Runtime presence-події (online/offline/typing) передаються через Event.

    Presence ::= ENUMERATED { offline (1), online (2), ... }

    PresenceOp ::= ENUMERATED {
       get  (1),
       list (2), ...
    }

    -- get зазвичай очікує actor
    -- list допускає actor і/або feed як фільтр вибірки
    -- feed задає контекст (якщо presence залежить від feed)
    PresenceQuery ::= SEQUENCE {
       op     PresenceOp,
       actor  [0] OCTET STRING OPTIONAL,
       feed   [1] MessageFeed OPTIONAL,
       ...
    }

    PresenceItem ::= SEQUENCE {
       actor     OCTET STRING,
       presence  Presence
    }

    -- get зазвичай повертає item
    -- list повертає items (може бути пустим)
    PresenceAnswer ::= SEQUENCE {
       item   [0] PresenceItem OPTIONAL,
       items  [1] SEQUENCE OF item PresenceItem OPTIONAL,
       ...
    }


    -- PersonStatus описує лише стан самого profile/state запису.
    -- Relation, lifecycle і moderation більше не живуть у Person:
    --   req/auth/ignore/friend -> Subscription / Event
    --   ban/banned             -> ModerationQuery / Event
    PersonStatus ::= ENUMERATED {
       active      (1),
       deleted     (2),
       nonexistent (3), ...
    }

    -- lastmsg не є частиною Person state.
    -- View-дані повинні передаватися через Query (Inbox/Search) або Event.
    Person ::= SEQUENCE {
       id OCTET STRING,
       nickname OCTET STRING,
       avatar OCTET STRING,
       names SEQUENCE OF name OCTET STRING,
       phone OCTET STRING,
       surnames SEQUENCE OF name OCTET STRING,
       presence Presence,
       update INTEGER,
       created INTEGER,
       settings SEQUENCE OF feature Feature OPTIONAL,
       status PersonStatus,
       ...
    }

    PersonOp ::= ENUMERATED {
       get    (1),
       list   (2),
       update (3),
       remove (4), ...
    }

    -- get/remove очікують id
    -- update використовує поля профілю
    -- list допускає частковий фільтр

    PersonQuery ::= SEQUENCE {
       op   PersonOp,

       id   [0] OCTET STRING OPTIONAL,
       name [1] OCTET STRING OPTIONAL,
       ...
    }

    PersonItem ::= SEQUENCE {
       id       OCTET STRING,
       nickname OCTET STRING,
       presence Presence,
       status   PersonStatus
    }

    -- get/update зазвичай повертають item
    -- list повертає items

    PersonAnswer ::= SEQUENCE {
       item   [0] PersonItem OPTIONAL,
       items  [1] SEQUENCE OF item PersonItem OPTIONAL,
       ...
    }

    Server ::= SEQUENCE { service OCTET STRING, port INTEGER, host OCTET STRING }

    -- RosterStatus описує лише стан roster як ресурсу.
    -- Command, mutation і lookup більше не живуть у Roster:
    --   get/create/del/remove/add/update/list/patch -> Query
    --   nick/search/contact/lastmsg                 -> Query / view

    RosterStatus ::= ENUMERATED {
       active   (1),
       archived (2),
       deleted  (3), ...
    }

    -- Roster є агрегованим snapshot/view ресурсом.
    -- Операції над roster передаються через Query.
    -- Runtime-події не живуть у Roster як моделі.

    Roster ::= SEQUENCE {
       id OCTET STRING,
       vsn Version,
       session OCTET STRING,
       nickname OCTET STRING,
       keys SEQUENCE OF key OCTET STRING,
       people SEQUENCE OF contact Person,
       topics SEQUENCE OF room Conference,
       channels SEQUENCE OF room Conference,
       servers SEQUENCE OF server Server,
       update INTEGER,
       status RosterStatus, ... }

    RosterOp ::= ENUMERATED {
       get  (1),
       list (2), ...
    }

    -- get зазвичай очікує id
    -- list допускає частковий фільтр

    RosterQuery ::= SEQUENCE {
       op   RosterOp,
       id   [0] OCTET STRING OPTIONAL,
       name [1] OCTET STRING OPTIONAL,
       ...
    }

    RosterItem ::= SEQUENCE {
       id       OCTET STRING,
       nickname OCTET STRING,
       status   RosterStatus
    }

    -- get зазвичай повертає item
    -- list повертає items

    RosterAnswer ::= SEQUENCE {
       item   [0] RosterItem OPTIONAL,
       items  [1] SEQUENCE OF item RosterItem OPTIONAL,
       ...
    }

    RosterCore ::= CHOICE {
       request [1] RosterQuery,
       result  [2] RosterAnswer
    }

    ModerationOp ::= ENUMERATED {
       ban    (1),
       unban  (2),
       list   (3), ...
    }

    -- ban/unban очікують actor + target
    -- list повертає список обмежень

    ModerationQuery ::= SEQUENCE {
       op     ModerationOp,
       actor  [0] OCTET STRING OPTIONAL,
       target [1] OCTET STRING OPTIONAL,
       ...
    }

    ModerationItem ::= SEQUENCE {
       actor   OCTET STRING,
       target  OCTET STRING
    }

    -- ban/unban зазвичай повертають item
    -- list повертає items

    ModerationAnswer ::= SEQUENCE {
       item   [0] ModerationItem OPTIONAL,
       items  [1] SEQUENCE OF item ModerationItem OPTIONAL,
       ...
    }

    ModerationExtension ::= CHOICE {
       request [1] ModerationQuery,
       result  [2] ModerationAnswer
    }

    -- 08 Conference (RocksDB, Multi-user Conferences)

    -- MemberStatus описує лише роль учасника в конференції.
    -- Lifecycle і mutation більше не живуть у Member:
    --   removed        -> Event / Query
    --   patch/update   -> Query
    MemberStatus ::= ENUMERATED {
       member (1),
       admin  (2),
       owner  (3), ...}

    Member ::= SEQUENCE {
       id OCTET STRING,
       nickname OCTET STRING,
       feed MessageFeed,
       feeds SEQUENCE OF feed OCTET STRING,
       phone OCTET STRING,
       avatar OCTET STRING,
       names SEQUENCE OF name OCTET STRING,
       surnames SEQUENCE OF name OCTET STRING,
       alias OCTET STRING,
       update INTEGER,
       settings SEQUENCE OF feature Feature,
       presence Presence,
       status MemberStatus, ... }

    MemberOp ::= ENUMERATED {
       get    (1),
       list   (2),
       add    (3),
       remove (4),
       update (5)
    }

    -- get/remove/update очікують actor + feed
    -- add використовує actor + feed
    -- list допускає фільтр за feed

    MemberQuery ::= SEQUENCE {
       op    MemberOp,

       actor [0] OCTET STRING OPTIONAL,
       feed  [1] MessageFeed OPTIONAL
    }

    MemberItem ::= SEQUENCE {
       actor   OCTET STRING,
       feed    MessageFeed,
       status  MemberStatus,
       presence Presence OPTIONAL
    }

    -- get/add/update зазвичай повертають item
    -- list повертає items

    MemberAnswer ::= SEQUENCE {
       item   [0] MemberItem OPTIONAL,
       items  [1] SEQUENCE OF item MemberItem OPTIONAL
    }

    ConferenceType ::= ENUMERATED { group (1), channel (2), call (3) }

    -- ConferenceStatus описує лише стан конференції як ресурсу.
    -- Command, lifecycle і події більше не живуть у Conference:
    --   create/add/remove/patch/get/delete -> Query
    --   join/leave/joined/removed          -> Event
    --   mute/unmute                        -> Query / Event
    --   lastmsg                            -> Query (Inbox/Search) або Event

    ConferenceStatus ::= ENUMERATED {
       active   (1),
       archived (2),
       deleted  (3), ...
    }

    -- lastmsg не є частиною Conference state.
    -- View-дані повинні передаватися через Query (Inbox/Search) або Event.

    Conference ::= SEQUENCE {
       id OCTET STRING,
       vsn Version,
       session OCTET STRING,
       name OCTET STRING,
       links SEQUENCE OF link OCTET STRING,
       description OCTET STRING,
       settings SEQUENCE OF feature Feature,
       members SEQUENCE OF member Member,
       admins SEQUENCE OF member Member,
       data SEQUENCE OF fileId OCTET STRING OPTIONAL,
       type ConferenceType,
       tos OCTET STRING,
       unread INTEGER,
       mentions SEQUENCE OF contact INTEGER,
       update INTEGER,
       created INTEGER,
       status ConferenceStatus,
        ... }

    ConferenceOp ::= ENUMERATED {
       get     (1),
       list    (2),
       create  (3),
       update  (4),
       remove  (5), ...
    }

    -- get/remove очікують id
    -- create/update використовують поля конференції
    -- list допускає частковий фільтр

    ConferenceQuery ::= SEQUENCE {
       op    ConferenceOp,
       id    [0] OCTET STRING OPTIONAL,
       name  [1] OCTET STRING OPTIONAL,
       type  [2] ConferenceType OPTIONAL,
       ...
    }

    -- get/create/update зазвичай повертають item
    -- list повертає items

    ConferenceAnswer ::= SEQUENCE {
       item   [0] ConferenceItem OPTIONAL,
       items  [1] SEQUENCE OF item ConferenceItem OPTIONAL,
       ...
    }

    ConferenceItem ::= SEQUENCE {
       id    OCTET STRING,
       name  OCTET STRING,
       type  ConferenceType,
       status ConferenceStatus
    }

    ConferenceExtension ::= CHOICE {
       request [1] ConferenceQuery,
       result  [2] ConferenceAnswer
    }

    -- 09 CHAT-v2 Protocol Entities

    CHATProtocol ::= CHOICE {
       authority [1] Authority,
       message   [2] Message,
       event     [4] Event,
       query     [5] Query
    }

    CHATMessage ::= SEQUENCE {
       no INTEGER,
       headers SEQUENCE OF header OCTET STRING,
       body CHATProtocol }

END
